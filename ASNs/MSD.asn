MSDASN1V2
DEFINITIONS
AUTOMATIC TAGS ::=
BEGIN
    CurrentVersion::= INTEGER (2)
    ECallMessage ::= SEQUENCE {
        msdVersion INTEGER(0 .. 255),
        msd OCTET STRING (CONTAINING MSDMessage)
    }
    MSDMessage ::= SEQUENCE {
        msdStructure MSDStructure,
        ...
    }
    MSDStructure ::= SEQUENCE {
        messageIdentifier INTEGER(0 .. 255),
        control ControlType,
        vehicleIdentificationNumber VIN,
        vehiclePropulsionStorageType VehiclePropulsionStorageType,
        timestamp INTEGER(0 .. 4294967295),
        vehicleLocation VehicleLocation,
        vehicleDirection INTEGER(0 .. 255),
        recentVehicleLocationN1 VehicleLocationDelta OPTIONAL,
        recentVehicleLocationN2 VehicleLocationDelta OPTIONAL,
        numberOfPassengers INTEGER(0 .. 255) OPTIONAL,
        ...
    }
    ControlType ::= SEQUENCE {
        automaticActivation BOOLEAN,
        testCall BOOLEAN,
        positionCanBeTrusted BOOLEAN,
        vehicleType VehicleType
    }
    VehicleType ::= ENUMERATED {
        passengerVehicleClassM1 (1),
        busesAndCoachesClassM2 (2),
        busesAndCoachesClassM3 (3),
        lightCommercialVehiclesClassN1 (4),
        heavyDutyVehiclesClassN2 (5),
        heavyDutyVehiclesClassN3 (6),
        motorcyclesClassL1e (7),
        motorcyclesClassL2e (8),
        motorcyclesClassL3e (9),
        motorcyclesClassL4e (10),
        motorcyclesClassL5e (11),
        motorcyclesClassL6e (12),
        motorcyclesClassL7e (13),
        ...
    }
    VIN ::= SEQUENCE {
        isowmi PrintableString (SIZE(3)) (FROM("A".."H"|"J".."N"|"P"|"R".."Z"|"0".."9")),
        isovds PrintableString (SIZE(6)) (FROM("A".."H"|"J".."N"|"P"|"R".."Z"|"0".."9")),
        isovisModelyear PrintableString (SIZE(1)) (FROM("A".."H"|"J".."N"|"P"|"R".."Z"|"0".."9")),
        isovisSeqPlant PrintableString (SIZE(7)) (FROM("A".."H"|"J".."N"|"P"|"R".."Z"|"0".."9"))
    }
    VehiclePropulsionStorageType ::= SEQUENCE {
        gasolineTankPresent BOOLEAN DEFAULT FALSE,
        dieselTankPresent BOOLEAN DEFAULT FALSE,
        compressedNaturalGas BOOLEAN DEFAULT FALSE,
        liquidPropaneGas BOOLEAN DEFAULT FALSE,
        electricEnergyStorage BOOLEAN DEFAULT FALSE,
        hydrogenStorage BOOLEAN DEFAULT FALSE,
        otherStorage BOOLEAN DEFAULT FALSE,
        ...
    }
    VehicleLocation ::= SEQUENCE {
        positionLatitude INTEGER(-2147483648..2147483647),
        positionLongitude INTEGER(-2147483648..2147483647)
    }
    VehicleLocationDelta ::= SEQUENCE {
        latitudeDelta INTEGER (-512..511),
        longitudeDelta INTEGER (-512..511)
    }
END
